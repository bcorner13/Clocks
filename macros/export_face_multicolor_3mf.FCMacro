# export_face_multicolor_3mf.FCMacro
# Export a clock face as a multi-object multi-color 3MF. Each object -> one filament slot in the
# slicer (Creality Print "load as multi-part object: Yes" groups them + colors per part).
#
#   SPLIT_BEZEL = False -> 2 objects: [disc] + [text]
#   SPLIT_BEZEL = True  -> 3 objects: [base] + [bezel lip] + [text]
#       The bezel object is ONLY the proud rim lip: the outer ring (r > FaceDiameter/2 - BezelWidth)
#       AND above the dial face (Z > FacePlateThickness). Everything else (the flat base plate +
#       dial) stays the base colour. So the bezel is its own colour WITHOUT hand-painting.
#
# "text" = all FCCircularText Part::Extrusion glyphs combined into ONE object. World positions
# preserved (text stays proud on the dial). Output: <project>/3mf/<DocLabel>.3mf
#
# Run on the ACTIVE face document. Meshes in a throwaway doc so the face doc is never touched.
# Does NOT write per-object slot metadata (FreeCAD can't) — assign slots once after import.
import FreeCAD as App, Part, MeshPart, Mesh, os, math

LINEAR_DEFLECTION = 0.01
ANGULAR_DEFLECTION = math.radians(20)
SPLIT_BEZEL = True

# bezel-split geometry, resolved from Params when available
FACE_DIAMETER_PARAM = "FaceDiameter"
BEZEL_WIDTH_PARAM   = "BezelWidth"
DIAL_FACE_Z_PARAM   = "FacePlateThickness"
FACE_DIAMETER_FALLBACK = 120.0
BEZEL_WIDTH_FALLBACK   = 1.5
DIAL_FACE_Z_FALLBACK   = 1.5
PARAMS_LABEL = "Params"


def _mesh(shape):
    return MeshPart.meshFromShape(Shape=shape, LinearDeflection=LINEAR_DEFLECTION,
                                  AngularDeflection=ANGULAR_DEFLECTION, Relative=False)


def _param(name, fallback):
    pdoc = next((d for d in App.listDocuments().values()
                 if d.Label == PARAMS_LABEL or d.Name == PARAMS_LABEL), None)
    if pdoc is not None:
        vs = pdoc.getObject("VarSet")
        if vs is not None and name in vs.PropertiesList:
            return float(getattr(vs, name))
    return fallback


def _bezel_cut_radius():
    return _param(FACE_DIAMETER_PARAM, FACE_DIAMETER_FALLBACK) / 2.0 - _param(BEZEL_WIDTH_PARAM, BEZEL_WIDTH_FALLBACK)


def run():
    doc = App.ActiveDocument
    if doc is None:
        print("No active document — open the face first."); return
    body = doc.getObject("Body")
    if body is None or not getattr(body, "Shape", None) or body.Shape.Volume <= 0:
        print("No solid Body found in", doc.Name); return
    exs = [o for o in doc.Objects if o.TypeId == "Part::Extrusion" and o.Shape and o.Shape.Volume > 0]

    label = doc.Label
    parts = []   # (suffix, mesh)

    bb = body.Shape.BoundBox
    cx, cy = bb.Center.x, bb.Center.y   # disc XY centre — do NOT assume origin

    did_split = False
    if SPLIT_BEZEL:
        r = _bezel_cut_radius()
        zc = _param(DIAL_FACE_Z_PARAM, DIAL_FACE_Z_FALLBACK)   # dial face height
        cyl = Part.makeCylinder(r, (bb.ZLength + 20),
                                App.Vector(cx, cy, bb.ZMin - 10), App.Vector(0, 0, 1))
        outer = body.Shape.cut(cyl)                            # outer ring, full height
        box_above = Part.makeBox(bb.XLength + 50, bb.YLength + 50, (bb.ZMax - zc) + 20,
                                 App.Vector(bb.XMin - 25, bb.YMin - 25, zc))
        bezel = outer.common(box_above)                        # outer ring ABOVE dial face = proud lip
        # only split if a real bezel lip exists on this face (virgin faces may have none)
        if bezel.Volume > 1e-3:
            base = body.Shape.cut(bezel)
            parts.append(("base",  _mesh(base)))
            parts.append(("bezel", _mesh(bezel)))
            did_split = True
            print(f"  bezel = proud lip (r>{round(r,3)}, Z>{zc}) -> base vol {round(base.Volume,1)}, bezel vol {round(bezel.Volume,1)}")
        else:
            print(f"  no bezel lip above Z={zc} at r>{round(r,3)} — exporting disc whole")
    if not did_split:
        parts.append(("disc", _mesh(body.Shape)))

    # text is optional — a face may have no FCCircularText glyphs yet
    if exs:
        parts.append(("text", _mesh(Part.makeCompound([e.Shape for e in exs]))))
    else:
        print("  (no text extrusions — exporting body parts only)")

    exp = App.newDocument("_exp_tmp")
    try:
        feats = []
        for suffix, m in parts:
            f = exp.addObject("Mesh::Feature", suffix); f.Mesh = m; f.Label = label + "-" + suffix
            feats.append(f)
        out_dir = os.path.join(os.path.dirname(doc.FileName), "3mf")
        os.makedirs(out_dir, exist_ok=True)
        out = os.path.join(out_dir, label + ".3mf")
        Mesh.export(feats, out)
    finally:
        App.closeDocument("_exp_tmp")

    print(f"wrote {len(parts)}-object 3MF:", out)
    print("  objects:", ", ".join(s for s, _ in parts),
          ("| text glyphs combined: " + str(len(exs))) if exs else "")


run()
